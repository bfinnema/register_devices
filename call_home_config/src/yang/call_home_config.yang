module call_home_config {

  namespace "http://example.com/call_home_config";
  prefix call_home_config;

  import ietf-inet-types {
    prefix inet;
  }
  import tailf-common {
    prefix tailf;
  }
  import tailf-ncs {
    prefix ncs;
  }
  import devreglic {
    prefix devreglic;
  }

  description
    "Call Home Config";

  revision 2020-11-13 {
    description
      "Initial revision.";
  }

  augment /devreglic:devreglic {

    list call_home_config {
      description "This is an RFS skeleton service";

      key name;
      leaf name {
        tailf:info "Unique service id";
        tailf:cli-allow-range;
        type string;
      }

      uses ncs:service-data;
      ncs:servicepoint call_home_config-servicepoint;

      leaf device-group {
        type leafref {
          path "/ncs:devices/ncs:device-group/ncs:name";
        }
      }
    }

  }

}
